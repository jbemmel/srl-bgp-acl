module bgp-acl-agent {

    yang-version "1";

    namespace "urn:srl_extension/bgp-acl-agent";

    prefix "bgp_acl_agent";

    import srl_nokia-acl {
        prefix _acl;
    }
    import srl_nokia-extensions {
      prefix srl_nokia-ext;
    }
    import srl_nokia-common {
      prefix srl_nokia-comm;
    }
    import srl_nokia-network-instance {
        prefix srl_nokia-netinst;
    }
    import srl_nokia-bgp {
        prefix srl_nokia-bgp;
    }

    // organization "Nokia";

    revision "2021-06-28" {
        description "Initial revision";
        reference "TBD";
    }

    grouping bgp-acl-agent-top {
        description "Top level grouping for BGP ACL agent sample app";

        container bgp-acl-agent {
            presence "presence container";
            description "Top level enclosing container for BGP ACL agent app
                         config and global operational state data";

            must "/system/gnmi-server/unix-socket/admin-state = 'enable'" {
              error-message "This agent requires the gNMI Unix socket to be enabled";
            }

            leaf acl-sequence-start {
                description "Initial sequence number to use for generated ACL entries";
                type uint16;
                default 1000;
            }

            leaf acl-count {
                config false;
                description "Total number of ACL entries created (ipv4/ipv6)";
                type uint32;
                default 0;
            }

            leaf last-change {
                config false;
                description "Date and time of last update (add/delete)";
                type srl_nokia-comm:date-and-time-delta;
            }

            //list entry {
            //    config false;

            //    key ip; // by making this a list with a key field, we can search for it

            //    leaf ip {
            //       description "Client source IP from which BGP sessions are initiated";
            //       type string; // IPv4/v6 address
            //    }

            //    leaf sequence-id {
            //       description "Sequence number of corresponding ACL entry";
            //       type uint16 {
            //         range "1..65535";

                     // Could define this as a reference to the ACL entry
            //       }
            //    }
            // }
        }
    }

    // data definition statements
    // uses bgp-acl-agent-top;
    // Depends on 'bgp' tree being present in the config
    augment "/srl_nokia-netinst:network-instance/srl_nokia-netinst:protocols/srl_nokia-bgp:bgp" {
        uses bgp-acl-agent-top;
    }

    // Add a flag to ACL entries such that we can easily track the ones we added
    grouping custom-agent-config {

     // Add a flag that is visible in the CLI, such that users can see
     leaf created-by-bgp-acl-agent {
        description "Timestamp added by BGP ACL agent to mark this entry";
        type string; // no point to make this srl_nokia-comm:date-and-time-delta;

        must "(../match/protocol = 'tcp' or ../match/next-header = 'tcp') and (../match/destination-port/value = 179 or ../match/source-port/value = 179)" {
          error-message "The BGP ACL agent only manages TCP entries for port 179";
        }
     }
    }

    // Add custom state to ipv4 and ipv6 ACL entries
    augment "/_acl:acl/_acl:cpm-filter/_acl:ipv4-filter/_acl:entry" {
      uses custom-agent-config;
    }
    augment "/_acl:acl/_acl:cpm-filter/_acl:ipv6-filter/_acl:entry" {
      uses custom-agent-config;
    }

}
